FME workspace YLRE-puller.fmw

Parameters:
- SourceDataset_GEOJSON = $(FME_MF_DIR)GiC_Helsinki_TestSite.geojson   # Source GeoJSON File or URL
- SourceDataset_WFS = https://kartta.hel.fi/ws/geoserver/avoindata/wfs   # Source WFS (Web Feature Service) URL
- DestDataset_GEOJSON = /Users/juho-pekka.virtanen/Documents/GiC-DT-Processes/output/YLRE_Niitty.geojson   # Destination GeoJSON File
- DestDataset_SHAPEFILE = /Users/juho-pekka.virtanen/Documents/GiC-DT-Processes/output   # Destination Esri Shapefile Folder
- DestDataset_GEOJSON_4 = /Users/juho-pekka.virtanen/Documents/GiC-DT-Processes/output/YLRE_Pelto.geojson   # Destination GeoJSON File
- DestDataset_GEOTIFF_3 = /Users/juho-pekka.virtanen/Documents/GiC-DT-Processes/output/rasterized   # Destination GeoTIFF Folder
- DestDataset_GEOTIFF = /Users/juho-pekka.virtanen/Documents/GiC-DT-Processes/output/rasterized   # Destination GeoTIFF Folder

Readers:
- GEOJSON_1: GEOJSON from $(SourceDataset_GEOJSON) in LL84
- WFS_1: WFS from $(SourceDataset_WFS) in EPSG:3879

Writers:
- GEOJSON_2: GEOJSON to $(DestDataset_GEOJSON) in LL84
- SHAPEFILE_1: SHAPEFILE to $(DestDataset_SHAPEFILE)
- GEOJSON_3: GEOJSON to $(DestDataset_GEOJSON_4)
- GEOTIFF_1: GEOTIFF to $(DestDataset_GEOTIFF)
- GEOTIFF_2: GEOTIFF to $(DestDataset_GEOTIFF_3)

GiC_Helsinki_TestSite (reader GEOJSON_1)
    attributes: HelsinkiSite string
    -> To_GK25FIN
To_GK25FIN: Reprojector
    DEST = EPSG:3879
    INTERPOLATION_TYPE = ,NearestNeighbor
    RASTER_CELL_SIZE_LOOKUP = ,PreserveCells
    RASTER_TOLERANCE = 0.0
    SOURCE = LL84
    INTERPOLATION_TYPE_NAME = Nearest Neighbor
    RASTER_CELL_SIZE = Preserve Cells
    REPROJECTED -> From_testsite [CLIPPER]
YLRE_Viherosat_alue (reader WFS_1)
    attributes: gml_parent_id xml_buffer, gml_parent_property xml_buffer, gml_id xml_buffer, osan_id xml_real64, paakohde_tyyppi_id xml_real64, paakohde_tyyppi_id.xsi_nil xml_boolean, paatyyppi xml_buffer, paatyyppi.xsi_nil xml_boolean, alakohde_tyyppi_id xml_real64, alakohde_tyyppi_id.xsi_nil xml_boolean, alatyyppi xml_buffer, alatyyppi.xsi_nil xml_boolean, materiaali_id xml_real64, materiaali_id.xsi_nil xml_boolean, materiaali xml_buffer, materiaali.xsi_nil xml_boolean, rakenteellinen_kunnossapito xml_buffer, rakenteellinen_kunnossapito.xsi_nil xml_boolean, talvikunnossapito xml_buffer, talvikunnossapito.xsi_nil xml_boolean, tkp_kiireellisyys_lk xml_buffer, tkp_kiireellisyys_lk.xsi_nil xml_boolean, viher_hoitoluokka_id xml_real64, viher_hoitoluokka_id.xsi_nil xml_boolean, hoitoluokka xml_buffer, hoitoluokka.xsi_nil xml_boolean, hoitoluokan_selite xml_buffer, hoitoluokan_selite.xsi_nil xml_boolean, puhtaanapito xml_buffer, puhtaanapito.xsi_nil xml_boolean,
      puhtaanapito_vyohyke xml_buffer, puhtaanapito_vyohyke.xsi_nil xml_boolean, osan_pituus xml_real64, osan_pituus.xsi_nil xml_boolean, osan_leveys xml_real64, osan_leveys.xsi_nil xml_boolean, osan_pinta_ala xml_real64, osan_pinta_ala.xsi_nil xml_boolean, puiston_nimi xml_buffer, puiston_nimi.xsi_nil xml_boolean, viheralueen_kayttotarkoitus xml_buffer, viheralueen_kayttotarkoitus.xsi_nil xml_boolean, viheralueen_id xml_real64, viheralueen_id.xsi_nil xml_boolean, viheralueen_nro xml_int64, viheralueen_nro.xsi_nil xml_boolean, osan_nro xml_int64, osan_nro.xsi_nil xml_boolean, paivitetty_pvm xml_date, paivitetty_pvm.xsi_nil xml_boolean, paivitetty_tietopalveluun xml_date, paivitetty_tietopalveluun.xsi_nil xml_boolean, geom xml_geometry
    -> From_testsite [CANDIDATE]
From_testsite: Clipper
    ADD_NODATA = YES
    BOUNDARY_CASES = INSIDE
    CLEANING_TOLERANCE_LOOKUP = AUTO
    CLIPPED_ATTR = _clipped
    GENERATE_LIST = NO
    INVALID_PARTS_HANDLING = REJECT_WHOLE
    MISSING_M_MODE_LOOKUP = LINEAR
    MISSING_Z_MODE_LOOKUP = PLANAR
    MULTIPLE_CLIPPERS = NO
    M_VAL_SOURCE = CANDIDATE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> To_WGS84
To_WGS84: Reprojector
    DEST = LL84
    INTERPOLATION_TYPE = ,NearestNeighbor
    RASTER_CELL_SIZE_LOOKUP = ,PreserveCells
    RASTER_TOLERANCE = 0.0
    SOURCE = EPSG:3879
    INTERPOLATION_TYPE_NAME = Nearest Neighbor
    RASTER_CELL_SIZE = Preserve Cells
    REPROJECTED -> BulkAttributeRemover
BulkAttributeRemover
    ATTR_EXP = @Value(_clipped)
    -> Pick_specific_subtypes
Pick_specific_subtypes: AttributeFilter
    ATTR_NAME = alatyyppi
    ATTR_VALUES = <Empty>,Pelto,Niityt,A, niitto 2 x, jäte poistetaan,B, niitto 1 x, jäte poistetaan,C, niitto 2 x, jätettä ei poisteta,D, niitto 1 x, jätettä ei poisteta,Nurmikko,<Missing>,<Null>,<Unfiltered>
    Pelto -> To_GK25FIN_2
    Pelto -> YLRE_Pelto (writer GEOJSON_3)
    Pelto -> FeatureColorSetter
    Niityt -> YLRE_Niitty (writer GEOJSON_2)
    Niityt -> To_GK25FIN_3
    Niityt -> FeatureColorSetter_2
YLRE_Pelto (writer GEOJSON_3)
    attributes: gml_parent_id string, gml_parent_property string, gml_id string, osan_id float, paakohde_tyyppi_id float, paakohde_tyyppi_id.xsi_nil boolean, paatyyppi string, paatyyppi.xsi_nil boolean, alakohde_tyyppi_id float, alakohde_tyyppi_id.xsi_nil boolean, alatyyppi string, alatyyppi.xsi_nil boolean, materiaali_id float, materiaali_id.xsi_nil boolean, materiaali string, materiaali.xsi_nil boolean, rakenteellinen_kunnossapito string, rakenteellinen_kunnossapito.xsi_nil boolean, talvikunnossapito string, talvikunnossapito.xsi_nil boolean, tkp_kiireellisyys_lk string, tkp_kiireellisyys_lk.xsi_nil boolean, viher_hoitoluokka_id float, viher_hoitoluokka_id.xsi_nil boolean, hoitoluokka string, hoitoluokka.xsi_nil boolean, hoitoluokan_selite string, hoitoluokan_selite.xsi_nil boolean, puhtaanapito string, puhtaanapito.xsi_nil boolean,
      puhtaanapito_vyohyke string, puhtaanapito_vyohyke.xsi_nil boolean, osan_pituus float, osan_pituus.xsi_nil boolean, osan_leveys float, osan_leveys.xsi_nil boolean, osan_pinta_ala float, osan_pinta_ala.xsi_nil boolean, puiston_nimi string, puiston_nimi.xsi_nil boolean, viheralueen_kayttotarkoitus string, viheralueen_kayttotarkoitus.xsi_nil boolean, viheralueen_id float, viheralueen_id.xsi_nil boolean, viheralueen_nro int, viheralueen_nro.xsi_nil boolean, osan_nro int, osan_nro.xsi_nil boolean, paivitetty_pvm string, paivitetty_pvm.xsi_nil boolean, paivitetty_tietopalveluun string, paivitetty_tietopalveluun.xsi_nil boolean, geom string, _clipped string
YLRE_Niitty (writer GEOJSON_2)
    attributes: gml_parent_id string, gml_parent_property string, gml_id string, osan_id float, paakohde_tyyppi_id float, paakohde_tyyppi_id.xsi_nil boolean, paatyyppi string, paatyyppi.xsi_nil boolean, alakohde_tyyppi_id float, alakohde_tyyppi_id.xsi_nil boolean, alatyyppi string, alatyyppi.xsi_nil boolean, materiaali_id float, materiaali_id.xsi_nil boolean, materiaali string, materiaali.xsi_nil boolean, rakenteellinen_kunnossapito string, rakenteellinen_kunnossapito.xsi_nil boolean, talvikunnossapito string, talvikunnossapito.xsi_nil boolean, tkp_kiireellisyys_lk string, tkp_kiireellisyys_lk.xsi_nil boolean, viher_hoitoluokka_id float, viher_hoitoluokka_id.xsi_nil boolean, hoitoluokka string, hoitoluokka.xsi_nil boolean, hoitoluokan_selite string, hoitoluokan_selite.xsi_nil boolean, puhtaanapito string, puhtaanapito.xsi_nil boolean,
      puhtaanapito_vyohyke string, puhtaanapito_vyohyke.xsi_nil boolean, osan_pituus float, osan_pituus.xsi_nil boolean, osan_leveys float, osan_leveys.xsi_nil boolean, osan_pinta_ala float, osan_pinta_ala.xsi_nil boolean, puiston_nimi string, puiston_nimi.xsi_nil boolean, viheralueen_kayttotarkoitus string, viheralueen_kayttotarkoitus.xsi_nil boolean, viheralueen_id float, viheralueen_id.xsi_nil boolean, viheralueen_nro int, viheralueen_nro.xsi_nil boolean, osan_nro int, osan_nro.xsi_nil boolean, paivitetty_pvm string, paivitetty_pvm.xsi_nil boolean, paivitetty_tietopalveluun string, paivitetty_tietopalveluun.xsi_nil boolean, geom string, _clipped string
FeatureColorSetter
    ALGORITHM = MANUAL
    COLOR = 0.945098,1,0.411765
    FILL_COLOR = 0.956863,1,0.796078
    MODE = Fixed
    COLORED -> ImageRasterizer
ImageRasterizer
    ALPHA = 1.0
    ANTI_ALIASING = No
    BACKGROUND_ALPHA = 0.0
    BACKGROUND_COLOR = 1,1,1
    COLUMNS = 2000
    FILL_WITH_NODATA = No
    INTERPRETATION_TYPE_LOOKUP = RGBA32
    ROWCOL_OR_CELLSIZE = RowsColumns
    ROWS = 2000
    SPECIFY_GROUND_EXTENTS = Use input data ground extents
    TOLERANCE = 0.5
    INTERPRETATION_TYPE = RGBA32
    RASTER -> YLRE_pelto (writer GEOTIFF_1)
YLRE_pelto (writer GEOTIFF_1)
FeatureColorSetter_2
    ALGORITHM = MANUAL
    COLOR = 0.772549,0.988235,0.439216
    FILL_COLOR = 0.862745,0.992157,0.788235
    MODE = Fixed
    COLORED -> ImageRasterizer_2
ImageRasterizer_2
    ALPHA = 1.0
    ANTI_ALIASING = No
    BACKGROUND_ALPHA = 0.0
    BACKGROUND_COLOR = 1,1,1
    COLUMNS = 2000
    FILL_WITH_NODATA = No
    INTERPRETATION_TYPE_LOOKUP = RGBA32
    ROWCOL_OR_CELLSIZE = RowsColumns
    ROWS = 2000
    SPECIFY_GROUND_EXTENTS = Use input data ground extents
    TOLERANCE = 0.5
    INTERPRETATION_TYPE = RGBA32
    RASTER -> YLRE_niitty (writer GEOTIFF_2)
YLRE_niitty (writer GEOTIFF_2)
To_GK25FIN_3: Reprojector
    DEST = EPSG:3879
    INTERPOLATION_TYPE = ,NearestNeighbor
    RASTER_CELL_SIZE_LOOKUP = ,PreserveCells
    RASTER_TOLERANCE = 0.0
    SOURCE = LL84
    INTERPOLATION_TYPE_NAME = Nearest Neighbor
    RASTER_CELL_SIZE = Preserve Cells
    REPROJECTED -> YLRE_Niitty (writer SHAPEFILE_1)
YLRE_Niitty (writer SHAPEFILE_1)
    attributes: gml_parent varchar(254), gml_pare00 varchar(254), gml_id varchar(254), osan_id double, paakohde_t double, paakohde00 logical, paatyyppi varchar(254), paatyyppi_ logical, alakohde_t double, alakohde00 logical, alatyyppi varchar(254), alatyyppi_ logical, materiaali varchar(254), materiaa00 logical, materiaali varchar(254), materiaa01 logical, rakenteell varchar(254), rakentee00 logical, talvikunno varchar(254), talvikun00 logical, tkp_kiiree varchar(254), tkp_kiir00 logical, viher_hoit double, viher_ho00 logical, hoitoluokk varchar(254), hoitoluo00 logical, hoitoluoka varchar(254), hoitoluo01 logical, puhtaanapi varchar(254), puhtaana00 logical,
      puhtaana01 varchar(254), puhtaana02 logical, osan_pituu double, osan_pit00 logical, osan_levey double, osan_lev00 logical, osan_pinta double, osan_pin00 logical, puiston_ni varchar(254), puiston_00 logical, viheraluee varchar(254), viheralu00 logical, viheralu01 double, viheralu02 logical, viheralu03 number(20,0), viheralu04 logical, osan_nro number(20,0), osan_nro_x logical, paivitetty varchar(254), paivitet00 logical, paivitet01 varchar(254), paivitet02 logical, geom varchar(254), Q__clipped varchar(3)
To_GK25FIN_2: Reprojector
    DEST = EPSG:3879
    INTERPOLATION_TYPE = ,NearestNeighbor
    RASTER_CELL_SIZE_LOOKUP = ,PreserveCells
    RASTER_TOLERANCE = 0.0
    SOURCE = LL84
    INTERPOLATION_TYPE_NAME = Nearest Neighbor
    RASTER_CELL_SIZE = Preserve Cells
    REPROJECTED -> YLRE_Pelto (writer SHAPEFILE_1)
YLRE_Pelto (writer SHAPEFILE_1)
    attributes: gml_parent varchar(254), gml_pare00 varchar(254), gml_id varchar(254), osan_id double, paakohde_t double, paakohde00 logical, paatyyppi varchar(254), paatyyppi_ logical, alakohde_t double, alakohde00 logical, alatyyppi varchar(254), alatyyppi_ logical, materiaali varchar(254), materiaa00 logical, materiaali varchar(254), materiaa01 logical, rakenteell varchar(254), rakentee00 logical, talvikunno varchar(254), talvikun00 logical, tkp_kiiree varchar(254), tkp_kiir00 logical, viher_hoit double, viher_ho00 logical, hoitoluokk varchar(254), hoitoluo00 logical, hoitoluoka varchar(254), hoitoluo01 logical, puhtaanapi varchar(254), puhtaana00 logical,
      puhtaana01 varchar(254), puhtaana02 logical, osan_pituu double, osan_pit00 logical, osan_levey double, osan_lev00 logical, osan_pinta double, osan_pin00 logical, puiston_ni varchar(254), puiston_00 logical, viheraluee varchar(254), viheralu00 logical, viheralu01 double, viheralu02 logical, viheralu03 number(20,0), viheralu04 logical, osan_nro number(20,0), osan_nro_x logical, paivitetty varchar(254), paivitet00 logical, paivitet01 varchar(254), paivitet02 logical, geom varchar(254), Q__clipped varchar(3)
